module config-firewall {
    namespace "http://netgroup.ipv6.polito.it/vnf";
    prefix "firewall";
    import ietf-inet-types { 
		prefix inet; 
	}
    description "Firewall configuration";

	container interfaces { 
		list ifEntry{
		    key "name";
		    leaf name {
				description "name='Name'";
				type string;
			}
			leaf mac-address{
			    description "name='MAC Address'";
			    type string;
			    mandatory false;
			}
			leaf management{
			    description "name='Management'";
			    type boolean;
			    mandatory false;
			}
			container ipv4_configuration{
			    presence "it contains ipv4 configuration";
			    leaf configurationType{
			        description "name='Configuration type'";
			        type enumeration {
                        enum dhcp;
                        enum static;
    				}
			    }
			    leaf address{
			        description "name='IP Address";
			        type inet:ipv4-address;
			        mandatory false;
			    }
			    leaf netmask{
			        description "name='Netmask";
			        type inet:ip-address;
			        mandatory false;
			    }
			    leaf default_gw{
			        description "name='Default GW";
			        type inet:ipv4-address;
			        mandatory false;
			    }
			}
			container ipv6_configuration{
			    presence "it contains ipv4 configuration";
			    leaf configurationType{
			        description "name='Configuration type'";
			        type enumeration {
                        enum dhcp;
                        enum static;
    				}
			    }
			    leaf address{
			        description "name='IP Address";
			        type inet:ipv6-address;
			        mandatory false;
			    }
			    leaf netmask{
			        description "name='Netmask";
			        type inet:ip-address;
			        mandatory false;
			    }
			    leaf default_gw{
			        description "name='Default GW";
			        type inet:ipv6-address;
			        mandatory false;
			    }
			}
		}

	} 
       
	container firewall {
		description "name='Firewall";
		leaf wan-interface {
            description "name='WAN Interface";
            type leafref {
                path "/interfaces/ifEntry/name";
            }
            mandatory false;
        }
		list policies {
			key "policy-name";
			leaf policy-name {
				type string;
			}
			leaf description{
			    type string;
			}
			leaf action {
				type enumeration {
					enum drop;
					enum accept;
				}
			}
			leaf in-interface {
				type leafref {
				 	path "/interfaces/ifEntry/name";
				}
				mandatory false;
			}
			leaf out-interface {
				type leafref {
				 	path "/interfaces/ifEntry/name";
				}
				mandatory false;
			}
			leaf source-address {
				type inet:ip-address;
			}
			leaf source-mask {
				type inet:ip-address;
				mandatory false;
			}
			leaf destination-address {
				type inet:ip-address;
				mandatory false;
			}
			leaf destination-mask {
				type inet:ip-address;
				mandatory false;
			}
			leaf protocol {
				type enumeration {
					enum tcp;
					enum udp;
					enum icmp;
					enum all;
				}
			}
			leaf source-port {
				type string;
				mandatory false;
			}
			leaf destination-port {
				type string;
				mandatory false;
			}
		}
		list blacklist {
		    key "uri";
		    description "name='URL', tooltip='eg: www.youtube.com'";
		    leaf uri{
		        type string;
		    }
		}
		list whitelist {
		    key "uri";
		    description "name='URL', tooltip='eg: www.youtube.com'";
		    leaf uri{
		        type string;
		    }
		}
	}
 }
