module config-nat { 
	namespace "http://netgroup.ipv6.polito.it/vnf"; 
	prefix "nat"; 
	import ietf-inet-types { 
		prefix inet; 
	} 
	description "Nat configuration";

	container nat{
	    leaf wan-interface {
				type leafref {
				 	path "/interfaces/ifEntry/name";
				}
				mandatory false;
        }
        container staticBindings{
                list floatingIP {
              description "name='Floating IP'";
                      key "public_address";
                      leaf private_address {
                               description "name='Private address'";
                               type inet:ip-address;
                         }
                      leaf public_address {
                               description "name='Public address'";
                               type inet:ip-address;
                         }
                }
        }
    }
	container interfaces {
		description "name='Interfaces list'";
		list ifEntry {
			description "name='Iface'";
			key "name";
			leaf name {
				description "name='Name'";
				type string;
			}
			leaf configurationType {
				description "name='Configuration type'";
				type enumeration {
					enum dhcp;
					enum static;
					enum not_defined;
				}
			}
			leaf mac_address{
			    type string;
			    mandatory false;
			}
			leaf address {
				description "name='IP Address'";
                mandatory false;
				type inet:ip-address;
			}
			leaf netmask{
			    mandatory false;
			    type uint32;
			}
			leaf default_gw {
				description "name='Default GW'";
                mandatory false;
				type inet:ip-address;
			}
			leaf management{
			    mandatory false;
			    type boolean;
			}
		}
	}
}
