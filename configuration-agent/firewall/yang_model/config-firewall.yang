module config-firewall {
    namespace "http://netgroup.ipv6.polito.it/vnf";
    prefix "firewall";
    import ietf-inet-types { 
		prefix inet; 
	}
    description "Firewall configuration";

	container interfaces { 
		list ifEntry{
		    key "name";
		    min-elements 2;
		    max-elements 3;
		    atomic true;
		    advertise onchange;
		    leaf name {
				description "name='Name'";
				type string;
			}
			leaf type{
			    description "name='Type'";
			    type enumeration {
                    enum L3;
                    enum transparent;
                    enum not_defined;
    			}
			}
			leaf management{
			    description "name='Management'";
			    type boolean;
			    mandatory false;
			}
			container ipv4_configuration{
			    presence "it contains ipv4 configuration";
			    advertise onchange;
			    leaf configurationType{
			        description "name='Configuration type'";
			        type enumeration {
                        enum dhcp;
                        enum static;
                        enum not_defined;
    				}
			    }
			    leaf address{
			        description "name='IP Address";
			        type inet:ipv4-address;
			        mandatory false;
			    }
			    leaf netmask{
			        description "name='Netmask";
			        type inet:ip-address;
			        mandatory false;
			    }
			    leaf mac_address{
                    description "name='MAC Address'";
                    type inet:mac-address;
                    mandatory false;
			    }
			    leaf default_gw{
			        description "name='Default GW";
			        type inet:ipv4-address;
			        mandatory false;
			    }
			}
			container ipv6_configuration{
			    presence "it contains ipv4 configuration";
			    leaf configurationType{
			        description "name='Configuration type'";
			        type enumeration {
                        enum dhcp;
                        enum static;
                        enum not_defined;
    				}
			    }
			    leaf address{
			        description "name='IP Address";
			        type inet:ipv6-address;
			        mandatory false;
			    }
			    leaf netmask{
			        description "name='Netmask";
			        type inet:ip-address;
			        mandatory false;
			    }
			    leaf default_gw{
			        description "name='Default GW";
			        type inet:ipv6-address;
			        mandatory false;
			    }
			}
		}
		leaf wan-interface {
            description "name='WAN Interface";
            type leafref {
                path "/interfaces/ifEntry/name";
            }
            mandatory false;
            advertise ondemand;
        }
	} 
       
	container firewall {
		description "name='Firewall";
		list policies {
			atomic true;
			advertise onchange;
			key "id";
			leaf id {
				type string;
			}
			leaf description{
			    type string;
			    mandatory false;
			}
			leaf action {
				type enumeration {
					enum drop;
					enum reject;
					enum accept;
				}
			}
			leaf protocol {
				type enumeration {
					enum tcp;
					enum udp;
					enum icmp;
					enum all;
				}
			}
			leaf in-interface {
				type leafref {
				 	path "/interfaces/ifEntry/name";
				}
				mandatory false;
			}
			leaf out-interface {
				type leafref {
				 	path "/interfaces/ifEntry/name";
				}
				mandatory false;
			}
			leaf src-address {
				type inet:ip-address;
			}
			leaf dst-address {
				type inet:ip-address;
				mandatory false;
			}
			leaf src-port {
				type inet:port-number;
				mandatory false;
			}
			leaf dst-port {
				type inet:port-number;
				mandatory false;
			}
		}
		list blacklist {
		    key "url";
		    description "name='URL', tooltip='eg: www.youtube.com'";
		    advertise onchange;
		    leaf url{
		        type string;
		    }
		}
		list whitelist {
		    key "url";
		    description "name='URL', tooltip='eg: www.youtube.com'";
		    advertise onchange;
		    leaf url{
		        type string;
		    }
		}
	}
 }
