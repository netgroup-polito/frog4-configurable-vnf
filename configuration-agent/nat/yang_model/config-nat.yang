module config-nat { 
	namespace "http://netgroup.ipv6.polito.it/vnf"; 
	prefix "nat"; 
	import ietf-inet-types { 
		prefix inet; 
	} 
	description "Nat configuration";

    container interfaces {
		description "name='Interfaces'";
		list ifEntry{
		    description "name='Interface'";
		    key "id";
		    min-elements 2;
		    max-elements 3;
		    atomic true;
		    advertise onchange;
			leaf id{
				description "name='ID'";
				type string;
			}
			leaf name {
				description "name='Name'";
				type string;
			}
			leaf type{
			    description "name='Type'";
			    type enumeration {
                    enum L3;
                    enum transparent;
                    enum not_defined;
    			}
			}
			leaf management{
			    description "name='Management privileges'";
			    type boolean;
			    mandatory false;
			}
			container ipv4_configuration{
			    presence "it contains ipv4 configuration";
			    leaf configurationType{
			        description "name='Configuration type'";
			        type enumeration {
                        enum dhcp;
                        enum static;
                        enum not_defined;
    				}
			    }
			    leaf address{
			        description "name='IP address";
			        type inet:ipv4-address;
			        mandatory false;
			    }
			    leaf netmask{
			        description "name='Netmask";
			        type inet:ip-address;
			        mandatory false;
			    }
			    leaf mac_address{
                    description "name='MAC Address'";
                    type inet:mac-address;
                    mandatory false;
			    }
			    leaf default_gw{
			        description "name='Default gateway";
			        type inet:ipv4-address;
			        mandatory false;
			    }
			}
			container ipv6_configuration{
			    presence "it contains ipv6 configuration";
			    leaf configurationType{
			        description "name='Configuration type'";
			        type enumeration {
                        enum dhcp;
                        enum static;
                        enum not_defined;
    				}
			    }
			    leaf address{
			        description "name='IP address";
			        type inet:ipv6-address;
			        mandatory false;
			    }
			    leaf netmask{
			        description "name='Netmask";
			        type inet:ip-address;
			        mandatory false;
			    }
			    leaf default_gw{
			        description "name='Default gateway";
			        type inet:ipv6-address;
			        mandatory false;
			    }
			}
		}
     }

	container nat{
		description "name='Nat";
		leaf private-interface {
		    description "name='Private Interface";
		    type leafref {
			    path "/interfaces/ifEntry/id";
		    }
		    advertise ondemand;
		}
		leaf public-interface {
		    description "name='Public Interface";
		    type leafref {
			    path "/interfaces/ifEntry/id";
		    }
		    advertise ondemand;
		}
		container nat-table{
		    description "name='Nat Table'";
		    list nat-session {
			    description "name='Nat Session'";
                advertise onchange;
                atomic true;
                leaf protocol {
                    description "name='Protocol'";
                    type enumeration {
                    enum ICMP;
                    enum TCP;
                    enum UDP;
                    }
                }
                leaf src_address {
                    description "name='Source Address'";
                    type inet:ip-address;
                }
                leaf src_port {
                    description "name='Source Port'";
                    type inet:port-number;
                }
                leaf dst_address {
                    description "name='Destination address'";
                    type inet:ip-address;
                }
                leaf dst_port {
                    description "name='Destination port'";
                    type inet:port-number;
                }
                leaf translated_address {
                    description "name='Translated address'";
                    type inet:ip-address;
                }
                leaf translated_port {
                        description "name='Destination port'";
                    type inet:port-number;
                }
                leaf tcp_state {
                    description "name='TCP state'";
                    type enumeration {
                    enum NONE;
                    enum SYN_SENT;
                    enum SYN_RECV;
                    enum ESTABLISHED;
                    enum FIN_WAIT;
                    enum CLOSE_WAIT;
                    enum LAST_ACK;
                    enum TIME_WAIT;
                    enum CLOSE;
                    enum LISTEN;
                    }
                    mandatory false;
                }
		    }
		}
		container arp-table{
		    description "name='ARP table'";
		    atomic true;
		    advertise onchange;
		    list arp-entry{
                description "name='ARP entry'";
                key "ip_address";
                leaf ip_address{
                    description "name='IP address'";
                    type inet:ip-address;
                }
                leaf mac_address{
                    description "name='MAC address'";
                    type inet:mac-address;
                }
		    }
		}
		}
		list floatingIP {
		    description "name='Floating IP'";
		    key "public_address";
		    atomic true;
		    advertise onchange;
		    leaf private_address {
                description "name='Private address'";
                type inet:ip-address;
		    }
		    leaf public_address {
                description "name='Public address'";
                type inet:ip-address;
		    }
		}
}
