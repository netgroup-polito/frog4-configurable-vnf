module config-iperf {
	namespace "http://netgroup.ipv6.polito.it/iperf";
	prefix "iperf";
	import ietf-inet-types {
		prefix inet;
	}

    container interfaces {
        list ifEntry{
            key "id";
            min-elements 2;
            max-elements 3;
            leaf id{
				description "name='ID'";
				type string;
			}
            leaf name {
                description "name='Name'";
                type string;
            }
            leaf type{
                description "name='Type'";
                type enumeration {
                        enum L3;
                        enum transparent;
                        enum not_defined;
                    }
            }
            leaf management{
                description "name='Management'";
                type boolean;
                mandatory false;
            }
            container ipv4_configuration{
                presence "it contains ipv4 configuration";
                leaf configurationType{
                    description "name='Configuration type'";
                    type enumeration {
                        enum dhcp;
                        enum static;
                    }
                }
                leaf address{
                    description "name='IP Address";
                    type inet:ipv4-address;
                    mandatory false;
                }
                leaf netmask{
                    description "name='Netmask";
                    type inet:ip-address;
                    mandatory false;
                }
                leaf mac_address{
                    description "name='MAC Address'";
                    type string;
                    mandatory false;
                }
                leaf default_gw{
                    description "name='Default GW";
                    type inet:ipv4-address;
                    mandatory false;
                }
            }
            container ipv6_configuration{
                presence "it contains ipv4 configuration";
                leaf configurationType{
                    description "name='Configuration type'";
                    type enumeration {
                        enum dhcp;
                        enum static;
                    }
                }
                leaf address{
                    description "name='IP Address";
                    type inet:ipv6-address;
                    mandatory false;
                }
                leaf netmask{
                    description "name='Netmask";
                    type inet:ip-address;
                    mandatory false;
                }
                leaf default_gw{
                    description "name='Default GW";
                    type inet:ipv6-address;
                    mandatory false;
                }
            }
        }
    }

    container iperf{
        container server{
            leaf address{
                type inet:ipv4-address;
            }
            leaf port{
                type string;
            }
        }
        container client{
            leaf server_address{
                type inet:ipv4-address;
            }
            leaf server_port{
                type string;
            }
            leaf protocol{
                type enumeration{
                    enum tcp;
                    enum udp;
                }
                default tcp;
                mandatory false;
            }
            leaf duration{
                description "default is 10 secs"
                type integer;
                default 10;
                mandatory false;
            }
            leaf bidirectional{
                description "The Iperf server connects back to the client allowing the bi-directional bandwidth measurement. By default, only the bandwidth from the client to the server is measured."
                type boolean;
                default false;
                mandatory false;
            }
            leaf bitrate{
                description "target bitrate in bits/sec. By default 1 Mbit/sec for UDP, unlimited for TCP."
                type integer;
                default false;
                mandatory false;
            }
        }
    }
}
