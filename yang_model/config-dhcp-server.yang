module config-dhcp-server { 
	namespace "http://netgroup.ipv6.polito.it/dhcp"; 
	prefix "dhcp";
	import ietf-inet-types { 
		prefix inet; 
	}

	container interfaces {
		list ifEntry{
		    key "name";
		    leaf name {
				description "name='Name'";
				type string;
			}
			leaf type{
			    description "name='Type'";
			    type boolean;
			    type enumeration {
                        enum L3;
                        enum transparent;
    				}
			}
			leaf management{
			    description "name='Management'";
			    type boolean;
			    mandatory false;
			}
			container ipv4_configuration{
			    presence "it contains ipv4 configuration";
			    leaf configurationType{
			        description "name='Configuration type'";
			        type enumeration {
                        enum dhcp;
                        enum static;
    				}
			    }
			    leaf address{
			        description "name='IP Address";
			        type inet:ipv4-address;
			        mandatory false;
			    }
			    leaf netmask{
			        description "name='Netmask";
			        type inet:ip-address;
			        mandatory false;
			    }
			    leaf mac-address{
                    description "name='MAC Address'";
                    type string;
                    mandatory false;
			    }
			    leaf default_gw{
			        description "name='Default GW";
			        type inet:ipv4-address;
			        mandatory false;
			    }
			}
			container ipv6_configuration{
			    presence "it contains ipv4 configuration";
			    leaf configurationType{
			        description "name='Configuration type'";
			        type enumeration {
                        enum dhcp;
                        enum static;
    				}
			    }
			    leaf address{
			        description "name='IP Address";
			        type inet:ipv6-address;
			        mandatory false;
			    }
			    leaf netmask{
			        description "name='Netmask";
			        type inet:ip-address;
			        mandatory false;
			    }
			    leaf default_gw{
			        description "name='Default GW";
			        type inet:ipv6-address;
			        mandatory false;
			    }
			}
		}
	}

	description "DHCP Server configuration"; 
	container server { 
		description "name='Server'";
		container globalIpPool { 
		description "name='Global IP pool'";
			container gatewayIp { 
				description "name='Gateway IP'";
				leaf gatewayAddress {
					description "name='IP Address'";
					type inet:ipv4-address; 
				} 
				leaf gatewayMask { 
					description "tooltip='name='Netmask', Gateway IP Address Mask'"; 
					type inet:ipv4-address; 
				} 
			} 
			list sections { 
				description "name='Pools'";
				key "sectionStartIp"; 
				leaf sectionStartIp { 
					description "name='Pool start IP', tooltip='IP Address'"; 
					type inet:ipv4-address; 
					mandatory "true"; 
				} 
				leaf sectionEndIp { 
					description "name='Pool end IP', tooltip='IP Address'";  
					type inet:ipv4-address; 
					mandatory "false"; 
				} 
				
			} 
			leaf defaultLeaseTime { 
				description "name='Default lease time', tooltip='Specifies the lease time in seconds, option code is 51.'"; 
				type string; 
			} 
			leaf maxLeaseTime { 
				description "name='Max lease time', tooltip='Specifies the lease time in seconds, option code is 51.'"; 
				type string;
			} 
			container dns {
				leaf primaryServer {
				    description "name='Primary Server', tooltip='Specifies the primary server, option code is 5.'";
				    type inet:ip-address;
				}
				leaf secondaryServer {
				    description "name='Secondary Server', tooltip='Specifies the secondary server, option code is 5.'";
				    type inet:ip-address;
				    mandatory "false";
				}
				leaf domainName {
				    description "name='DNS name', tooltip='Specifies the domain name, option code is 15.'";type string;
				}
			}

		}
		list clients {
			key "mac_address";
			leaf mac_address {
				description "name='MAC Address'";
				type string;
			}
			leaf ip_address {
				description "name='IP Address'";
				type string;
			}
			leaf hostname{
			    description "name='Hostname'";
			    type inet:ip-address;
			}
			leaf valid_until{
			    description "name='Valid until'";
			    type string;
			}
		}
	}

}
